package 'Metadata Example-1' {
  metadata def SafetyFeature;

  metadata def SecurityFeature {
    :> annotatedElement : SysML::PartDefinition;
    :> annotatedElement : SysML::PartUsage;
  }

  metadata SafetyFeature about vehicle::interior::seatBelt, vehicle::interior::driverAirBag, vehicle::bodyAssy::bumper;

  metadata SecurityFeature about vehicle::interior::alarm, vehicle::bodyAssy::keylessEntry;

  part vehicle {
    part interior {
      part alarm;

      part seatBelt[2];

      part frontSeat[2];

      part driverAirBag;
    }

    part bodyAssy {
      part body;

      part bumper;

      part keylessEntry;
    }
  }
}
